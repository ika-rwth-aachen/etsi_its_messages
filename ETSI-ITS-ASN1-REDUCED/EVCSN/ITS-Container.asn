ITS-Container {
itu-t (0) identified-organization (4) etsi (0) itsDomain (5) wg1 (1) ts (102894) cdd (2) version (1) 
}

DEFINITIONS AUTOMATIC TAGS ::=

BEGIN

ItsPduHeader ::= SEQUENCE {
	protocolVersion INTEGER{currentVersion(1)} (0..255),
	messageID INTEGER{denm(1),cam(2), poi(3), spat(4), map(5), ivi(6), ev-rsr(7)} (0..255),
	stationID StationID
}

StationID ::= INTEGER(0..4294967295)

ReferencePosition ::= SEQUENCE {
	latitude Latitude,
	longitude Longitude,
	positionConfidenceEllipse PosConfidenceEllipse ,
	altitude Altitude
}

Longitude ::= INTEGER {oneMicrodegreeEast (10), oneMicrodegreeWest (-10), unavailable(1800000001)} (-1800000000..1800000001)

Latitude ::= INTEGER {oneMicrodegreeNorth (10), oneMicrodegreeSouth (-10), unavailable(900000001)} (-900000000..900000001)

Altitude ::= SEQUENCE {
	altitudeValue AltitudeValue,
	altitudeConfidence AltitudeConfidence
}

AltitudeValue ::= INTEGER {referenceEllipsoidSurface(0), oneCentimeter(1), unavailable(800001)} (-100000..800001)

AltitudeConfidence ::= ENUMERATED {
	alt-000-01 (0),
	alt-000-02 (1),
	alt-000-05 (2),
	alt-000-10 (3),
	alt-000-20 (4),
	alt-000-50 (5),
	alt-001-00 (6),
	alt-002-00 (7),
	alt-005-00 (8),
	alt-010-00 (9),
	alt-020-00 (10),
	alt-050-00 (11),
	alt-100-00 (12),
	alt-200-00 (13),
	outOfRange (14),
	unavailable (15)
}

PosConfidenceEllipse ::= SEQUENCE {
	semiMajorConfidence SemiAxisLength,
	semiMinorConfidence SemiAxisLength,
	semiMajorOrientation HeadingValue
}

SemiAxisLength ::= INTEGER{oneCentimeter(1), outOfRange(4094), unavailable(4095)} (0..4095)

HeadingValue ::= INTEGER {wgs84North(0), wgs84East(900), wgs84South(1800), wgs84West(2700), unavailable(3601)} (0..3601)

TimestampIts ::= INTEGER {utcStartOf2004(0), oneMillisecAfterUTCStartOf2004(1)} (0..4398046511103)

END
